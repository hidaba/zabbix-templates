--
-- Copyright 2010-2013 Ruckus Wireless, Inc. All rights reserved.
--
-- RUCKUS WIRELESS, INC. CONFIDENTIAL - 
-- This is an unpublished, proprietary work of Ruckus Wireless, Inc., and is 
-- fully protected under copyright and trade secret laws. You may not view, 
-- use, disclose, copy, or distribute this file or any information contained 
-- herein except pursuant to a valid license from Ruckus. 
--

RUCKUS-ROOT-MIB DEFINITIONS ::= BEGIN

IMPORTS
    enterprises,
    MODULE-IDENTITY
        FROM SNMPv2-SMI;

ruckusRootMIB MODULE-IDENTITY
    LAST-UPDATED "201510150800Z"
    ORGANIZATION "Ruckus Wireless, Inc."
    CONTACT-INFO
        "Ruckus Wireless, Inc.

        Postal:
        350 West Java Dr.
        Sunnyvale, CA 94089
        USA

        EMail: support@ruckuswireless.com

        Phone: +1-650-265-4200"
    DESCRIPTION
        "Ruckus top level mib."
    ::= { enterprises 25053 }


-- Groups
--

ruckusObjects OBJECT IDENTIFIER  ::= { ruckusRootMIB 1 }

ruckusCommon OBJECT IDENTIFIER   ::= { ruckusObjects 1 }

ruckusCommonTCModule OBJECT IDENTIFIER      ::= { ruckusCommon 1 }

ruckusUnleashed OBJECT IDENTIFIER   ::= { ruckusObjects 15 }

ruckusUnleashedSystemModule OBJECT IDENTIFIER      ::= { ruckusUnleashed 1 }

ruckusUnleashedWLANModule OBJECT IDENTIFIER        ::= { ruckusUnleashed 2 }

ruckusEvents OBJECT IDENTIFIER    ::= { ruckusRootMIB 2 }


END
